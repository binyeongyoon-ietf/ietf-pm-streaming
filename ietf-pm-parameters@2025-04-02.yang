module ietf-pm-parameters {
    yang-version 1.1;
    namespace "urn:ietf:params:xml:ns:yang:ietf-pm-parameters";
    prefix pm-param;

    organization
      "IETF CCAMP Working Group";

    contact
      "WG Web: <https://datatracker.ietf.org/wg/ccamp/>
       Editor: Bin Yeong Yoon
               <mailto:byyun@etri.re.kr>";

    description
      "This YANG module defines performance management parameters 
       based on ITU-T G.7710.";

    revision 2025-04-02 {
        description
          "Updated revision to define parameters.";
    }

    typedef maintenance-parameters { 
        type enumeration {
            enum es {
                description "Errored Second";
            }
            enum ses {
                description "Severely Errored Second";
            }
            enum bbe {
                description "Background Block Error";
            }
            enum bbc {
                description "Background Block Count";
            }
            enum uas {
                description "Unavailable Second";
            }                                       
        }
        description
            "Enumeration of performance parameters used for
            maintenance monitoring with 15 minute time 
            interval.";        
    }

    typedef maintenance-parameters-extended {
        type enumeration {
            enum es {
                description "Errored Second";
            }
            enum ses {
                description "Severely Errored Second";
            }
            enum bbe {
                description "Background Block Error";
            }
            enum bbc {
                description "Background Block Count";
            }
            enum uas {
                description "Unavailable Second";
            }                                       
            enum pje {
                description "Pointer Justification Event";
            }
        }
        description
            "Enumeration of performance parameters used for
            maintenance monitoring with 24 hour time 
            interval.";          
    }

    typedef qos-parameters {
        type enumeration {
            enum es {
                description "Errored Second";
            }
            enum ses {
                description "Severely Errored Second";
            }
            enum bbe {
                description "Background Block Error";
            }
            enum bbc {
                description "Background Block Count";
            }
            enum uas {
                description "Unavailable Second";
            }
            enum sep {
                description "Severely Errored Period";
            }
        }
        description
            "Enumeration of performance parameters used for
            QoS monitoring with 24 hours.";         
    }
   
}
