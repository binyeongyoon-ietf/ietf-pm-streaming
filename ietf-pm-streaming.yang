module ietf-pm-streaming {
  yang-version 1.1;
  namespace "urn:ietf:params:xml:ns:yang:ietf-pm-streaming";
  prefix pm-str;

  /*
  * Import YANG Type
  */
  import ietf-yang-types {
    prefix yang;
    reference
    "RFC 6991: Common YANG Data Types";
  }

  organization
    "IETF Common Control and Measurement Plane (ccamp)
    Working Group";

  contact
    "WG Web:    <https://datatracker.ietf.org/wg/ccamp/>
    Editor:     Bin Yeong Yoon
                <mailto:byyun@etri.re.kr>";

  description
    "This YANG module defines a data model for performance
    management streaming, based on ITU-T G.7710 for
    equipment. It specifies measurement types, performance
    parameters, their streaming subscriptions, and event
    notifications.";

  revision 2024-10-10 {
    description "Initial version";
  }

  /*
   * TYPEDEFs
   */
  typedef parameter-unit {
    type string;
    description
      "Unit of measurement for performance management
      parameters defined by network elements (servers).";
  }

  typedef maintenance-parameters {
    type enumeration {
      enum es {
        description
          "Errored Second";
      }
      enum ses {
        description
          "Severely Errored Second";
      }
      enum bbe {
        description
          "Background Block Error";
      }
      enum bbc {
        description
          "Background Block Count";
      }
      enum uas {
        description
          "Unavailable Second";
      }
    }
      description
        "Enumeration of performance parameters used for
        maintenance monitoring with 15 minute time
        interval.";
  }

  typedef maintenance-parameters-extended {
    type enumeration {
      enum es {
        description
          "Errored Second";
      }
      enum ses {
        description
          "Severely Errored Second";
      }
      enum bbe {
        description
          "Background Block Error";
      }
      enum bbc {
        description
          "Background Block Count";
      }
      enum uas {
        description
          "Unavailable Second";
      }
      enum pje {
        description
          "Pointer Justification Event";
      }
    }
    description
      "Enumeration of performance parameters used for
      maintenance monitoring with 24 hour time
      interval.";
  }

  typedef qos-parameters {
    type enumeration {
      enum es {
        description
          "Errored Second";
      }
      enum ses {
        description
          "Severely Errored Second";
      }
      enum bbe {
        description
          "Background Block Error";
      }
      enum bbc {
        description
          "Background Block Count";
      }
      enum uas {
        description
          "Unavailable Second";
      }
      enum sep {
        description
          "Severely Errored Period";
        }
    }
    description
      "Enumeration of performance parameters used for
      QoS monitoring with 24 hours.";
  }

  /*
   * GROUPINGS
   */

  grouping count-standing-condition-config {
    container standing-condition-config {
      description
        "Optional configuration, applicable only for 15-minute
        intervals of the count measurements";
      leaf standing-threshold {
        type uint32;
        description "configuring the standing threshold";
      }
      leaf standing-reset-threshold {
        type uint32;
        description
          "configuring the reset standing threshold";
      }
    }
  }

  grouping count-transient-condition-config {
    container transient-condition-config {
      uses out-of-range-config;
    }
  }

  grouping count-measurement-15min-gr {
    description
      "Counts are cumulative measurements that track the
      total occurrences of specific network events or
      activities over 15 minutes. Counts are reset at
      regular intervals to start fresh measurements.";

    container count-measurement {
      leaf count-value {
        type uint32;
        config false;
        description
          "The cumulative value of the count over the
          15-minute interval.";
      }
      leaf count-unit {
        type parameter-unit;
        config false;
        description
          "Unit of measurement for the count-value.";
      }
      uses count-transient-condition-config;
      uses count-standing-condition-config;
    }
  }

  grouping count-measurement-24hr-gr {
    description
        "Counts are cumulative measurements that track
        the total  occurrences of specific network
        events or activities over 24 hours. Counts are
        reset at regular intervals to start
        fresh measurements. ";

    container count-measurement {
      leaf count-value {
        type uint32;
        config false;
      }
      leaf count-unit {
        type parameter-unit;
        config false;
        description
            "Unit of measurement for the
            counts-value.";
      }
      uses count-transient-condition-config;
    }
  }

  grouping snapshot-measurement-gr{
    container snapshot-measurement {
      description
        "Snapshots are instantaneous measurements
        taken at a specific point in time. They
        provide a momentary view of network conditions.
        Snapshots are collected at pre-determined
        uniform times within fixed intervals (e.g.,
        every 15 minutes, 24 hours).";

      leaf uniform-time {
        type uint32;
        units "seconds";
        description
            "Consistent intervals for capturing
            network performance data.";
      }
      leaf snapshot-value {
        type uint32;
        config false;
      }
      leaf snapshot-unit {
        type parameter-unit;
        config false;
        description
            "Unit of measurement for the snapshot-value.";
      }
      uses out-of-range-config;
    }
  }

  grouping tidemark-measurement-gr{
    container tidemark-maintenance {
      description
        "Tidemarks record the highest (maximum) or lowest
        (minimum) values of a specific performance metric
        over a defined period, such as 15 minutes or 24
        hours. They are designed to capture extreme values
        that reflect significant performance peaks.";

      leaf high-tide-value {
        type uint32;
        config false;
      }
      leaf high-tide-unit {
        type parameter-unit;
        config false;
        description
          "Unit of measurement for the high-tide-value.";
      }
      leaf low-tide-value {
        type uint32;
        config false;
      }
      leaf low-tide-unit {
        type parameter-unit;
        config false;
        description
          "Unit of measurement for the low-tide-value.";
      }
      uses out-of-range-config;
    }
  }

  grouping out-of-range-config {
    description
      "An out-of-range (OOR) event is triggered to indicate
      an overflow or underflow condition when a measured
      metric exceeds its high threshold or falls below its
      low threshold. These events apply to count (transient),
      snapshot, and tidemark measurements.";

    leaf high-oor-threshold {
      type uint32;
      description
        "Configuring the high out of range (OOR) report";
    }
    leaf low-oor-threshold {
      type uint32;
      description
        "Configuring the low out of range (OOR) report";
    }
  }

  grouping event-state-info {
    leaf event-occurred {
      type boolean;
        description
          "Indicates whether an event occurs or not.";
    }
    leaf event-time {
      type yang:date-and-time;
        description
          "A timestamp indicating when the event occurred";
    }
  }

  grouping triggered-oor-event-info {
    uses oor-event-type;
    uses event-state-info;
  }

  grouping count-transient-event-gr {
    description
      "Threshold report (TR) is generated for the
      counter measurement when the threshold is
      reached or is reached or crossed for a given
      performance measurement";

    container count-transient-event {
      uses triggered-oor-event-info;
    }
  }

  grouping count-standing-event-gr {
    description
      "A Threshold Report (TR) is generated when the
      set threshold is exceeded, and a Reset Threshold
      Report (RTR) is issued at the end of the period
      if the value drops below or equals the reset
      threshold.";

    container count-standing-event {
      leaf event-type {
        description
          "Indicates whether TR or RTR was generated";

        type enumeration {
          enum Threshold-Report {
            description
              "High OOR threshold reached";
          }
          enum Reset-Threshold-Report {
            description
              "Low OOR threshold reached";
          }
        }
      }
      uses event-state-info;
    }
  }

  grouping snapshot-events-gr{
    description
      "High (or low) snapshot event is triggered
        as the high (or low) out of range when the
        snapshot value reaches or crosses the high
        (or low) threshold.";

    container snapshot-event{
      uses oor-event-type;
      leaf event-occurred {
        type boolean;
          description
            "Indicates whether the snapshot-value has
            reached the high(or low)-oor-threshold.";
      }
      leaf event-time {
          type yang:date-and-time;
              description
              "A timestamp indicating when the snapshot-value
              reached the high(or low)-oor-threshold";
      }
    }
  }

  grouping oor-event-type {
    leaf event-type {
      description
        "Indicates whether the high or low threshold
        was reached";

      type enumeration {
        enum High-OOR-event {
          description "High OOR threshold reached";
        }
        enum Low-OOR-event {
          description "Low OOR threshold reached";
        }
      }
    }
  }

  grouping tidemark-events-gr {
    description
      "High (or low) tidemark event is triggered
        as the high (or low) out of range when the
        tidemark value reaches or crosses the high
        (or low) threshold.";

    container tidemark-event {
      uses oor-event-type;
      leaf event-occurred {
        type boolean;
          description
              "Indicates whether the tidemark-value has
              reached the high(or low)-oor-threshold.";
      }
      leaf event-time {
        type yang:date-and-time;
          description
            "A timestamp indicating when the tidemark-
            value reached the high(or low)-oor-threshold";
      }
    }
  }

  grouping event-parameters-gr {
    container BUT-event {
      description
        "Begin Unavailable Time (BUT) event marking
        the start of a period when a network element
        or connection is unavailable.";

      uses event-state-info;
    }
    container EUT-event {
      description
        "End Unavailable Time (BUT) event marking the
        end of a period when a network element or
        connection was unavailable.";

      leaf event-occurred {
        type boolean;
        description
            "Indicates whether EUT event is generated.";
      }
      leaf event-time {
        type yang:date-and-time;
        description "End Unavailable Time (EUT)";
      }
      leaf total-unavailable-time {
        type uint32;
        units "seconds";
        description
          "Total duration of unavailability.";
      }
    }
    container CSES-event {
      description
        "A sequence of severely errored seconds (SES)
        event detected consecutively within a specified
        time frame.";

      leaf event-occurred {
        type boolean;
        description
          "Indicates whether CSES event is generated.";
      }
      leaf begin-time {
        type yang:date-and-time;
          description
              "A timestamp indicating when CSES period
              begins.";
      }
      leaf end-time {
        type yang:date-and-time;
        description
          "A timestamp indicating when CSES
          period ends.";
      }
      leaf duration {
        type uint32;
        units "seconds";
        description
          "Duration of the CSES period.";
      }
      leaf error-count {
        type uint32;
        description
          "Number of errors during the CSES period.";
      }
    }
  }

  /*
   * MAIN CONTAINER
   */

  container pm-periodic-measurement {
    description
      "This container includes PM periodic measurements,
      such as count, snapshot, and tidemark, used for
      maintenance and QoS monitoring. These measurements
      are typically taken over 15-minute and 24-hour
      intervals and are categorized by their purpose
      (maintenance/QoS) and time interval, as each case
      involves different parameter types.";

    leaf measurement-interval {
      type uint32 {
        range "1..max";
      }
      units "seconds";
      description
        "This interval defines the periodic measurement of
        PM parameters. Clients can select the interval based
        on the capabilities provided by network elements.";
    }
    container maintenance-15min {
      description
        "Contains metric value of the PM parameters
        by the measurement methods for maintenance
        monitoring with 15 minute time interval.";

      list pm-parameter {
        key "parameter-name";
        description
          "List PM parameters for maintenance with 15
          minute time interval.";

        leaf parameter-name {
          type maintenance-parameters;
          description
            "Name of the parameters for maintenance
            with 15 minute time interval.";
        }
        uses count-measurement-15min-gr;
        uses snapshot-measurement-gr;
        uses tidemark-measurement-gr;
      }
    }
    container maintenance-24hr {
      description
        "Contains metric value of the PM parameters
        by the measurement methods for maintenance
        monitoring with 24 hour time interval.";

      list pm-parameter {
        key "parameter-name";
        description
          "List PM parameters for maintenance with 24
          hour time interval.";

        leaf parameter-name {
          type maintenance-parameters-extended;
          description
            "Name of the parameters for maintenance
            with 24 hour interval.";
        }
        uses count-measurement-24hr-gr;
        uses snapshot-measurement-gr;
        uses tidemark-measurement-gr;
      }
    }

    container qos-24hr {
      description
            "Contains metric value of the PM parameters
            by the measurement methods for QoS
            monitoring with 24 hour time interval.";

      list pm-parameter {
        key "parameter-name";
            description
                "List PM parameters for QoS with 24
                hours;";

        leaf parameter-name {
            type qos-parameters;
            description
                "Name of the parameters for QoS with
                24 hour interval.";
        }
        uses count-measurement-24hr-gr;
      }
    }
  }

  /*
   * NOTIFICATIONS
   */

  notification threshold-events {
    container periodic-threshold-events {
      description
        " Contains threshold events of the periodic
        measurements including counts, snapshots,
        and tidemarks.";

      container maintenance-15min {
        description
          "Contains threshold events of the PM
          parameters for maintenance monitoring
          with 15 minute time interval.";

        list pm-parameter {
          key "parameter-name";
          description
            "List PM parameters for maintenance
            with 15 min;";

          leaf parameter-name {
            type maintenance-parameters;
            description
              "Name of the PM parameters for
              maintenance with 15 minute time
              interval.";
          }
          uses count-transient-event-gr;
          uses count-standing-event-gr;
          uses snapshot-events-gr;
          uses tidemark-events-gr;
        }
      }
      container maintenance-24hr {
        description
          "Contains threshold events of the PM
          parameters for maintenance monitoring
          with24 hour time interval.";

        list pm-parameter {
          key "parameter-name";
          description
            "List PM parameters for maintenance
            with 24 hours;";

          leaf parameter-name {
            type maintenance-parameters;
            description
                "Name of the PM parameters for
                maintenance with 24 hour time
                interval.";
          }
          uses count-transient-event-gr;
          uses snapshot-events-gr;
          uses tidemark-events-gr;
        }
      }
      container qos-24hr {
        description
          "Contains threshold events of the PM
          parameters for QoS monitoring with
          24 hour time interval.";

        list pm-parameter {
          key "parameter-name";
            description
              "List PM parameters for QoS
              with 24 hours time interval;";

          leaf parameter-name {
            type qos-parameters;
            description
              "Name of the PM parameters for
              QoS with 24 hour time interval.";
          }
          uses count-transient-event-gr;
        }
      }
    }
    container non-periodic-threshold-events {
      uses event-parameters-gr;
    }
  }
}
