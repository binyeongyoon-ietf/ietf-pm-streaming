module ietf-pm-parameters {
  yang-version 1.1;
  namespace "urn:ietf:params:xml:ns:yang:ietf-pm-parameters";
  prefix pm-param;

  organization
    "IETF Common Control and Measurement Plane (ccamp)
     Working Group";
  contact
    "WG Web: <https://datatracker.ietf.org/wg/ccamp/>
     Editor: Bin Yeong Yoon
       <mailto:byyun@etri.re.kr>";
  description
    "This YANG module defines performance management parameters
     for common transport equipment, based on ITU-T G.7710.

     Copyright (c) 2026 IETF Trust and the persons identified as
     authors of the code.  All rights reserved.";

  revision 2026-06-03 {
    description
      "Initial revision.";
    reference
      "RFC XXXX: A YANG Data Model for Performance Monitoring
       Streaming on Common Transport Equipment";
  }

  identity performance-parameter {
    description
      "Base identity for performance monitoring parameters.";
  }
  identity es {
    base performance-parameter;
    description "Errored Second.";
  }
  identity ses {
    base performance-parameter;
    description "Severely Errored Second.";
  }
  identity bbe {
    base performance-parameter;
    description "Background Block Error.";
  }
  identity bbc {
    base performance-parameter;
    description "Background Block Count.";
  }
  identity uas {
    base performance-parameter;
    description "Unavailable Second.";
  }
  identity pje {
    base performance-parameter;
    description "Pointer Justification Event.";
  }
  identity sep {
    base performance-parameter;
    description "Severely Errored Period.";
  }

  container maintenance-parameters-15min {
    config false;
    description
      "Transport maintenance parameters for the 15-minute
       monitoring interval.";
    leaf es {
      type uint32;
      units "seconds";
      description "Errored Second.";
    }
    leaf ses {
      type uint32;
      units "seconds";
      description "Severely Errored Second.";
    }
    leaf bbe {
      type uint32;
      units "errors";
      description "Background Block Error.";
    }
    leaf bbc {
      type uint32;
      units "blocks";
      description "Background Block Count.";
    }
    leaf uas {
      type uint32;
      units "seconds";
      description "Unavailable Second.";
    }
  }

  container maintenance-parameters-24hr {
    config false;
    description
      "Transport maintenance parameters for the 24-hour
       monitoring interval.";
    leaf es {
      type uint32;
      units "seconds";
      description "Errored Second.";
    }
    leaf ses {
      type uint32;
      units "seconds";
      description "Severely Errored Second.";
    }
    leaf bbe {
      type uint32;
      units "errors";
      description "Background Block Error.";
    }
    leaf bbc {
      type uint32;
      units "blocks";
      description "Background Block Count.";
    }
    leaf uas {
      type uint32;
      units "seconds";
      description "Unavailable Second.";
    }
    leaf pje {
      type uint32;
      units "events";
      description "Pointer Justification Event.";
    }
  }

  container qos-parameters-24hr {
    config false;
    description
      "Transport QoS parameters for the 24-hour monitoring
       interval.";
    leaf es {
      type uint32;
      units "seconds";
      description "Errored Second.";
    }
    leaf ses {
      type uint32;
      units "seconds";
      description "Severely Errored Second.";
    }
    leaf bbe {
      type uint32;
      units "errors";
      description "Background Block Error.";
    }
    leaf bbc {
      type uint32;
      units "blocks";
      description "Background Block Count.";
    }
    leaf uas {
      type uint32;
      units "seconds";
      description "Unavailable Second.";
    }
    leaf sep {
      type uint32;
      units "periods";
      description "Severely Errored Period.";
    }
  }
}
