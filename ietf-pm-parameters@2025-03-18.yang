module ietf-pm-parameters {
    yang-version 1.1;
    namespace "urn:ietf:params:xml:ns:yang:ietf-pm-parameters";
    prefix pm-param;

    organization
      "IETF CCAMP Working Group";

    contact
      "WG Web: <https://datatracker.ietf.org/wg/ccamp/>
       Editor: Bin Yeong Yoon
               <mailto:byyun@etri.re.kr>";

    description
      "This YANG module defines performance management parameters based on ITU-T G.7710.";

    revision 2025-03-18 {
        description
          "Initial revision for pm parameters.";
    }

    // Base identity for all performance parameters
    identity performance-parameter {
        description
          "Base identity for performance monitoring parameters.";
    }

    // Parameter identities
    identity es {
        base performance-parameter;
        description
          "Errored Second.";
    }

    identity ses {
        base performance-parameter;
        description
          "Severely Errored Second.";
    }

    identity bbe {
        base performance-parameter;
        description
          "Background Block Error.";
    }

    identity bbc {
        base performance-parameter;
        description
          "Background Block Count.";
    }

    identity uas {
        base performance-parameter;
        description
          "Unavailable Second.";
    }

    identity pje {
        base performance-parameter;
        description
          "Pointer Justification Event.";
    }

    identity sep {
        base performance-parameter;
        description
          "Severely Errored Period.";
    }

    // Keep the existing containers but add references to the identities
    container maintenance-parameters-15min {
        description
          "Parameters for 15-minute maintenance monitoring interval.";

        leaf es {
            type uint32;
            units "seconds";
            config false;
            description
              "Errored Second.";
            reference
              "Corresponds to 'es' identity.";
        }

        leaf ses {
            type uint32;
            units "seconds";
            config false;
            description
              "Severely Errored Second.";
            reference
              "Corresponds to 'ses' identity.";
        }

        leaf bbe {
            type uint32;
            units "errors";
            config false;
            description
              "Background Block Error.";
            reference
              "Corresponds to 'bbe' identity.";
        }

        leaf bbc {
            type uint32;
            units "blocks";
            config false;
            description
              "Background Block Count.";
            reference
              "Corresponds to 'bbc' identity.";
        }

        leaf uas {
            type uint32;
            units "seconds";
            config false;
            description
              "Unavailable Second.";
            reference
              "Corresponds to 'uas' identity.";
        }
    }

    container maintenance-parameters-24hr {
        description
          "Maintenance monitoring parameters with a 24-hour interval.";

        leaf es {
            type uint32;
            units "seconds";
            config false;
            description
              "Errored Second.";
            reference
              "Corresponds to 'es' identity.";
        }

        leaf ses {
            type uint32;
            units "seconds";
            config false;
            description
              "Severely Errored Second.";
            reference
              "Corresponds to 'ses' identity.";
        }

        leaf bbe {
            type uint32;
            units "errors";
            config false;
            description
              "Background Block Error.";
            reference
              "Corresponds to 'bbe' identity.";
        }

        leaf bbc {
            type uint32;
            units "blocks";
            config false;
            description
              "Background Block Count.";
            reference
              "Corresponds to 'bbc' identity.";
        }

        leaf uas {
            type uint32;
            units "seconds";
            config false;
            description
              "Unavailable Second.";
            reference
              "Corresponds to 'uas' identity.";
        }

        leaf pje {
            type uint32;
            units "events";
            config false;
            description
              "Pointer Justification Event.";
            reference
              "Corresponds to 'pje' identity.";
        }
    }

    container qos-parameters-24hr {
        description
          "QoS monitoring parameters with a 24-hour interval.";

        leaf es {
            type uint32;
            units "seconds";
            config false;
            description
              "Errored Second.";
            reference
              "Corresponds to 'es' identity.";
        }

        leaf ses {
            type uint32;
            units "seconds";
            config false;
            description
              "Severely Errored Second.";
            reference
              "Corresponds to 'ses' identity.";
        }

        leaf bbe {
            type uint32;
            units "errors";
            config false;
            description
              "Background Block Error.";
            reference
              "Corresponds to 'bbe' identity.";
        }

        leaf bbc {
            type uint32;
            units "blocks";
            config false;
            description
              "Background Block Count.";
            reference
              "Corresponds to 'bbc' identity.";
        }

        leaf uas {
            type uint32;
            units "seconds";
            config false;
            description
              "Unavailable Second.";
            reference
              "Corresponds to 'uas' identity.";
        }

        leaf sep {
            type uint32;
            units "periods";
            config false;
            description
              "Severely Errored Period.";
            reference
              "Corresponds to 'sep' identity.";
        }
    }
}
